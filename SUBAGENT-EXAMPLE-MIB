SUBAGENT-EXAMPLE-MIB DEFINITIONS ::= BEGIN

IMPORTS
    NOTIFICATION-GROUP, OBJECT-GROUP
        FROM SNMPv2-CONF
    DisplayString
        FROM SNMPv2-TC
    experimental, OBJECT-TYPE, NOTIFICATION-TYPE, Integer32, MODULE-IDENTITY
        FROM SNMPv2-SMI
;

subagentExampleMIB MODULE-IDENTITY
    LAST-UPDATED "202504050000Z"
    ORGANIZATION "Choripan-Systems LLC"
    CONTACT-INFO "marcelo_mourier@yahoo.com"
    DESCRIPTION  "Minimalistic MIB for an AgentX example."
         
    ::= { experimental 9999 }

ac1Temp OBJECT-TYPE
    SYNTAX      Integer32
    MAX-ACCESS  read-only
    STATUS      current
    DESCRIPTION "The current value (in degrees Celsius) of the A/C
                 Unit #1 temperature sensor."
    ::= { subagentExampleMIB 1 }

ac2Temp OBJECT-TYPE
    SYNTAX      Integer32
    MAX-ACCESS  read-only
    STATUS      current
    DESCRIPTION "The current value (in degrees Celsius) of the A/C
                 Unit #2 temperature sensor."
    ::= { subagentExampleMIB 2 }

ac3Temp OBJECT-TYPE
    SYNTAX      Integer32
    MAX-ACCESS  read-only
    STATUS      current
    DESCRIPTION "The current value (in degrees Celsius) of the A/C
                 Unit #3 temperature sensor."
    ::= { subagentExampleMIB 3 }

hiTempThreshold OBJECT-TYPE
    SYNTAX      Integer32
    MAX-ACCESS  read-write
    STATUS      current
    DESCRIPTION "The temperature value (in degrees Celsius) above
                 which to raise an A/C Unit High Temperature alarm."
    DEFVAL		{ 30 }
    ::= { subagentExampleMIB 4 }
    
acHiTempAlarmUnit OBJECT-TYPE
    SYNTAX      Integer32
    MAX-ACCESS  accessible-for-notify
    STATUS      current
    DESCRIPTION "The A/C Unit that raised a High Temperature alarm."
    ::= { subagentExampleMIB 5 }
    
acHiTempAlarmState OBJECT-TYPE
    SYNTAX      Integer32
    MAX-ACCESS  accessible-for-notify
    STATUS      current
    DESCRIPTION "Indicates the current state of the High Temperature
                 alarm: 0 means the alarm is inactive and 1 indicates
                 the alarm is active."
    ::= { subagentExampleMIB 6 }
    
acHiTempAlarmNotification NOTIFICATION-TYPE
    OBJECTS     { acHiTempAlarmUnit, acHiTempAlarmState }
    STATUS      current
    DESCRIPTION	"Trap to notify a High Temperature alarm on one of
                 the A/C Units."
    ::= { subagentExampleMIB 7 }

END
